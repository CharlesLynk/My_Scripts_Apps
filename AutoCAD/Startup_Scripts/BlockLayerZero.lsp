(defun C:BlockLayerZero ( / att_blk_ss blk att $att)
(setq att_blk_ss (ssget "X" '((0 . "INSERT") (66 . 1))))
(while (/= (ssname att_blk_ss 0) nil)
(setq blk (ssname att_blk_ss 0)
		   att (entnext blk)
)
(while (and (/= att nil) (/= (cdr (assoc 0 (entget att))) "SEQEND"))
(setq $att (vlax-ename->vla-object att))
(if (= (vla-get-layer $att) oldlayername)
  (vla-put-layer $att newlayername)
)
(setq att (entnext att))
)
(setq att_blk_ss (ssdel (ssname att_blk_ss 0) att_blk_ss))
)
(princ)
)
